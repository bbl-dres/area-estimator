FME workspace Swisstopo 3D Buildings.fmw

Parameters:
- Output = $(FME_MF_DIR)Input\Swisstopo 3D OBJ   # Select a Folder

Creator
    GEOMTYPE = Geometry Object
    NUM = 1
    CREATED -> FeatureReader_2 [INITIATOR]
Note: INPUT: / Swisstopo 3D Buildings GDB / Layer: Building_solid
FeatureReader_2
    ATTRIBUTES = separated/Floor,"OBJECTID,UUID,OBJEKTART,NAME_KOMPLETT,GEBAEUDE_NUTZUNG,GRUND_AENDERUNG,HERKUNFT,HERKUNFT_MONAT,HERKUNFT_JAHR,ORIGINAL_HERKUNFT,ERSTELLUNG_MONAT,ERSTELLUNG_JAHR,REVISION_JAHR,REVISION_MONAT,DATUM_ERSTELLUNG,DATUM_AENDERUNG,GELAENDEPUNKT,GESAMTHOEHE,EGID,GEBAEUDEEINHEIT",separated/Roof,"OBJECTID,UUID,OBJEKTART,NAME_KOMPLETT,GEBAEUDE_NUTZUNG,GRUND_AENDERUNG,HERKUNFT,HERKUNFT_MONAT,HERKUNFT_JAHR,ORIGINAL_HERKUNFT,ERSTELLUNG_JAHR,ERSTELLUNG_MONAT,REVISION_JAHR,REVISION_MONAT,DATUM_ERSTELLUNG,DATUM_AENDERUNG,DACH_MAX,DACH_MIN,EGID,GEBAEUDEEINHEIT",separated/Wall,"OBJECTID,UUID,OBJEKTART,NAME_KOMPLETT,GEBAEUDE_NUTZUNG,GRUND_AENDERUNG,HERKUNFT,HERKUNFT_MONAT,HERKUNFT_JAHR,ORIGINAL_HERKUNFT,ERSTELLUNG_MONAT,ERSTELLUNG_JAHR,REVISION_JAHR,REVISION_MONAT,DATUM_ERSTELLUNG,DATUM_AENDERUNG,GELAENDEPUNKT,GESAMTHOEHE,EGID,GEBAEUDEEINHEIT",solid/Building_solid,"OBJECTID,UUID,OBJEKTART,NAME_KOMPLETT,GEBAEUDE_NUTZUNG,GRUND_AENDERUNG,HERKUNFT,HERKUNFT_JAHR,HERKUNFT_MONAT,ORIGINAL_HERKUNFT,ERSTELLUNG_JAHR,ERSTELLUNG_MONAT,REVISION_JAHR,REVISION_MONAT,DATUM_AENDERUNG,DATUM_ERSTELLUNG,DACH_MAX,DACH_MIN,GELAENDEPUNKT,GESAMTHOEHE,EGID,GEBAEUDEEINHEIT",solid/Roof_solid,"OBJECTID,UUID,OBJEKTART,NAME_KOMPLETT,GEBAEUDE_NUTZUNG,GRUND_AENDERUNG,HERKUNFT,HERKUNFT_JAHR,HERKUNFT_MONAT,ORIGINAL_HERKUNFT,ERSTELLUNG_JAHR,ERSTELLUNG_MONAT,REVISION_JAHR,REVISION_MONAT,DATUM_AENDERUNG,DATUM_ERSTELLUNG,DACH_MAX,DACH_MIN,EGID,GEBAEUDEEINHEIT"
    ATTR_ACCUM_MODE = Only Use Result
    CLIP_TO_ENVELOPE = NO
    COMBINE_GEOM = Use Result
    DATASET = C:\Users\DavidRasner\Downloads\SWISSBUILDINGS3D_3_0.gdb
    FEATURETYPES = solid/Building_solid
    FORMAT = GEODATABASE_FILE
    GEODATABASE_FILE_ALIAS_MODE = NONE
    GEODATABASE_FILE_CACHE_MULTIPATCH_TEXTURES = yes
    GEODATABASE_FILE_CHECK_SIMPLE_GEOM = no
    GEODATABASE_FILE_CREATE_FEATURE_TABLES_FROM_DATA = Yes
    GEODATABASE_FILE_DISABLE_FEATURE_DATASET_ATTRIBUTE = Yes
    GEODATABASE_FILE_FEATURE_READ_MODE = Features
    GEODATABASE_FILE_IGNORE_NETWORK_INFO = yes
    GEODATABASE_FILE_IGNORE_RELATIONSHIP_INFO = yes
    GEODATABASE_FILE_MERGE_FEAT_LINKED_ANNOS = no
    GEODATABASE_FILE_QUERY_FEATURE_TYPES_FOR_MERGE_FILTERS = Yes
    GEODATABASE_FILE_READ_THREE_POINT_ARCS = no
    GEODATABASE_FILE_REMOVE_FEATURE_DATASET = NO
    GEODATABASE_FILE_RESOLVE_DOMAINS = no
    GEODATABASE_FILE_RESOLVE_SUBTYPE_NAMES = yes
    GEODATABASE_FILE_SIMPLE_DONUT_GEOMETRY = no
    GEODATABASE_FILE_SPLIT_COMPLEX_ANNOS = no
    GEODATABASE_FILE_SPLIT_COMPLEX_EDGES = no
    GEODATABASE_FILE_SPLIT_MULTI_PART_ANNOS = no
    GEODATABASE_FILE_STRIP_GUID_GLOBALID_BRACES = no
    GEODATABASE_FILE_TRANSLATE_SPATIAL_DATA_ONLY = no
    GEODATABASE_FILE_USE_SEARCH_ENVELOPE = NO
    GEOMETRY_TYPES = separated/Floor,"""SHAPE,fme_surface""",separated/Roof,"""SHAPE,fme_surface""",separated/Wall,"""SHAPE,fme_surface""",solid/Building_solid,"""SHAPE,fme_surface""",solid/Roof_solid,"""SHAPE,fme_surface"""
    INITIATOR_FIRST_OUTPUT = default
    INTERACT = NONE
    MAX_FEATURES = 100
    ORDER_RESULTS = No
    OUTPUT_ADD_SCHEMA_ATTRIBUTES = NO
    OUTPUT_FEATURES_DISPLAY = Schema and Data Features
    solid/Building_solid -> PythonCaller
Note: Python: / Repair mesh with trimesh, calculate volume
PythonCaller
    PYTHONSOURCE:
      import fmeobjects
      import trimesh
      import numpy as np
      import io
      import gc

      class FeatureProcessor(object):
          def __init__(self):
              self.feature_count = 0
              self.repaired_count = 0
              self.volumes_calculated = 0
              self.failed_count = 0

          def input(self, feature):
              self.feature_count += 1

              # Process the feature
              self.process_single_feature(feature)

              # Force garbage collection every 1000 features
              if self.feature_count % 1000 == 0:
                  gc.collect()

          def get_point_coords(self, point):
              """Extract coordinates from FMEPoint using getXYZ()"""
              try:
                  coords = point.getXYZ()
                  return [float(coords[0]), float(coords[1]), float(coords[2])]
              except Exception as e:
                  raise Exception(f"Failed to extract coordinates: {str(e)}")

          def get_mesh_diagnostics(self, mesh):
              """Get detailed diagnostics about mesh issues - scipy-free version"""
              diagnostics = []

              try:
                  # Basic properties
                  diagnostics.append(f"Vertices: {len(mesh.vertices)}")
                  diagnostics.append(f"Faces: {len(mesh.faces)}")
                  diagnostics.append(f"Watertight: {mesh.is_watertight}")

                  # Topological properties (these don't need scipy)
                  diagnostics.append(f"Euler number: {mesh.euler_number}")

                  # Try to get body count (might need scipy)
                  try:
                      diagnostics.append(f"Connected components: {mesh.body_count}")
                  except:
                      pass

                  # Check if it's a valid volume
                  diagnostics.append(f"Is volume: {mesh.is_volume}")
                  diagnostics.append(f"Is winding consistent: {mesh.is_winding_consistent}")

                  # Get unique edges count
                  try:
                      edges = mesh.edges_unique
                      diagnostics.append(f"Unique edges: {len(edges)}")
                  except:
                      pass

                  # Check for problems without scipy
                  if not mesh.is_watertight:
                      # Simple checks
                      if not mesh.is_winding_consistent:
                          diagnostics.append("ISSUE: Inconsistent face winding")
                      if not mesh.is_volume:
                          diagnostics.append("ISSUE: Not a valid volume")

                      # Check for duplicate faces manually
                      faces_sorted = np.sort(mesh.faces, axis=1)
                      unique_faces = len(np.unique(faces_sorted, axis=0))
                      if unique_faces < len(mesh.faces):
                          diagnostics.append(f"ISSUE: Duplicate faces: {len(mesh.faces) - unique_faces}")

                  # Bounding box (doesn't need scipy)
                  bounds = mesh.bounds
                  if bounds is not None:
                      size_x = bounds[1][0] - bounds[0][0]
                      size_y = bounds[1][1] - bounds[0][1]
                      size_z = bounds[1][2] - bounds[0][2]
                      diagnostics.append(f"Size: {size_x:.2f} x {size_y:.2f} x {size_z:.2f}")

              except Exception as e:
                  diagnostics.append(f"Diagnostic error: {str(e)}")

              return diagnostics

          def process_single_feature(self, feature):
              """Process with minimal memory footprint"""
              try:
                  geometry = feature.getGeometry()
                  if not geometry:
                      feature.setAttribute('volume', None)
                      feature.setAttribute('error', 'No geometry')
                      self.pyoutput(feature)
                      self.failed_count += 1
                      return

                  # Get geometry type info
                  geom_type = type(geometry).__name__
                  feature.setAttribute('input_geometry_type', geom_type)

                  mesh = None
                  conversion_method = None
                  error_detail = []

                  # Check if it's FMEMultiSurface
                  if isinstance(geometry, fmeobjects.FMEMultiSurface):
                      try:
                          mesh, conv_details = self.multi_surface_to_trimesh(geometry)
                          if mesh is not None:
                              conversion_method = 'multi_surface'
                          else:
                              error_detail.append("Conversion returned None")
                              if conv_details:
                                  error_detail.extend(conv_details[:5])
                      except Exception as e:
                          error_detail.append(f"Conversion exception: {str(e)}")
                          mesh = None

                  # If it's already a mesh
                  elif isinstance(geometry, fmeobjects.FMEMesh):
                      try:
                          mesh = self.convert_mesh_via_obj(geometry)
                          conversion_method = 'mesh_obj'
                      except Exception as e:
                          error_detail.append(f"Mesh conversion error: {str(e)}")

                  else:
                      error_detail.append(f'Unsupported geometry type: {geom_type}')

                  if mesh is not None:
                      # Get diagnostics before any processing
                      pre_repair_diagnostics = self.get_mesh_diagnostics(mesh)

                      # Try to calculate volume directly if already watertight
                      volume = None
                      repair_details = []

                      try:
                          if mesh.is_watertight:
                              # Already watertight, just calculate volume
                              volume = float(mesh.volume)
                              repair_details.append("Already watertight - no repair needed")
                              is_watertight = True
                              self.volumes_calculated += 1
                          else:
                              # Needs repair
                              is_watertight, volume, repair_details_str = self.enhanced_mesh_repair(mesh)
                              repair_details.append(repair_details_str)
                      except Exception as e:
                          # Volume calculation failed
                          volume = None
                          is_watertight = mesh.is_watertight
                          repair_details.append(f"Volume calculation error: {str(e)}")

                          # Get post-error diagnostics
                          post_diagnostics = self.get_mesh_diagnostics(mesh)
                          feature.setAttribute('mesh_diagnostics', ' <pipe> '.join(post_diagnostics))

                      # Set attributes based on results
                      if volume is not None:
                          feature.setAttribute('volume', float(volume))
                          feature.setAttribute('is_watertight', True)
                          feature.setAttribute('conversion_method', conversion_method)
                          feature.setAttribute('error', None)
                      else:
                          feature.setAttribute('volume', None)
                          feature.setAttribute('is_watertight', is_watertight)
                          feature.setAttribute('error', 'Volume calculation failed')
                          feature.setAttribute('mesh_diagnostics', ' <pipe> '.join(pre_repair_diagnostics))

                      feature.setAttribute('repair_details', ' <pipe> '.join(repair_details))
                      feature.setAttribute('vertex_count', len(mesh.vertices))
                      feature.setAttribute('face_count', len(mesh.faces))

                      del mesh
                  else:
                      feature.setAttribute('volume', None)
                      feature.setAttribute('error', 'Conversion failed')
                      feature.setAttribute('error_detail', ' <pipe> '.join(error_detail) if error_detail else 'Unknown error')
                      self.failed_count += 1

                  self.pyoutput(feature)

              except Exception as e:
                  feature.setAttribute('volume', None)
                  feature.setAttribute('error', 'Processing error')
                  feature.setAttribute('error_detail', f'Exception: {str(e)}')
                  self.pyoutput(feature)
                  self.failed_count += 1

          def multi_surface_to_trimesh(self, multi_surface):
              """Convert FMEMultiSurface to trimesh"""
              details = []

              try:
                  all_vertices = []
                  all_faces = []
                  vertex_offset = 0
                  successful_parts = 0

                  num_parts = multi_surface.numParts()

                  for i in range(num_parts):
                      try:
                          surface = multi_surface.getPartAt(i)

                          # For FMEFace objects, we need to get as area first
                          area = None
                          boundary = None

                          if hasattr(surface, 'getAsArea'):
                              try:
                                  area = surface.getAsArea()
                                  if area:
                                      # Try to get boundary from area
                                      if hasattr(area, 'getBoundaryAsCurve'):
                                          boundary = area.getBoundaryAsCurve()
                                      elif hasattr(area, 'getOuterBoundaryAsCurve'):
                                          boundary = area.getOuterBoundaryAsCurve()
                              except Exception as e:
                                  if i < 3:
                                      details.append(f"Part {i}: getAsArea failed: {str(e)}")

                          # Extract points from boundary
                          if boundary:
                              try:
                                  points = []
                                  num_points = boundary.numPoints()

                                  if num_points >= 3:
                                      # Extract all points using getXYZ()
                                      for j in range(num_points):
                                          pt = boundary.getPointAt(j)
                                          coords = self.get_point_coords(pt)
                                          points.append(coords)

                                      # Remove duplicate last point if closed
                                      if len(points) > 3:
                                          if (abs(points[0][0] - points[-1][0]) < 1e-6 and
                                              abs(points[0][1] - points[-1][1]) < 1e-6 and
                                              abs(points[0][2] - points[-1][2]) < 1e-6):
                                              points = points[:-1]

                                      # Add vertices
                                      all_vertices.extend(points)

                                      # Create triangles using fan triangulation
                                      num_verts = len(points)
                                      for j in range(1, num_verts - 1):
                                          all_faces.append([
                                              vertex_offset,
                                              vertex_offset + j,
                                              vertex_offset + j + 1
                                          ])

                                      vertex_offset += num_verts
                                      successful_parts += 1
                                  else:
                                      if i < 3:
                                          details.append(f"Part {i}: Only {num_points} points")
                              except Exception as e:
                                  if i < 3:
                                      details.append(f"Part {i}: Point extraction failed: {str(e)}")
                          else:
                              if i < 3:
                                  details.append(f"Part {i}: No boundary found")

                      except Exception as e:
                          if i < 3:
                              details.append(f"Part {i}: Exception: {str(e)}")

                  if successful_parts > 0:
                      details.append(f"Processed {successful_parts}/{num_parts} parts")

                  if all_vertices and all_faces:
                      # Process mesh to merge duplicate vertices
                      mesh = trimesh.Trimesh(
                          vertices=np.array(all_vertices),
                          faces=np.array(all_faces),
                          process=True  # Enable processing to merge vertices
                      )
                      return mesh, details
                  else:
                      details.append("No valid geometry created")
                      return None, details

              except Exception as e:
                  details.append(f"Fatal error: {str(e)}")
                  return None, details

          def enhanced_mesh_repair(self, mesh):
              """Enhanced mesh repair for building hulls - only for non-watertight meshes"""
              repair_steps = []

              try:
                  # Skip visual processing
                  if hasattr(mesh, 'visual'):
                      mesh.visual = None

                  # This should only be called for non-watertight meshes
                  if mesh.is_watertight:
                      volume = float(mesh.volume)
                      return True, volume, "Already watertight"

                  # Step 1: Merge duplicate vertices with tolerance
                  initial_vertices = len(mesh.vertices)
                  mesh.merge_vertices(digits=5)
                  merged_vertices = initial_vertices - len(mesh.vertices)
                  if merged_vertices > 0:
                      repair_steps.append(f"Merged {merged_vertices} duplicate vertices")

                  # Step 2: Remove degenerate faces
                  initial_faces = len(mesh.faces)
                  mesh.remove_degenerate_faces()
                  removed_faces = initial_faces - len(mesh.faces)
                  if removed_faces > 0:
                      repair_steps.append(f"Removed {removed_faces} degenerate faces")

                  # Step 3: Fix normals
                  mesh.fix_normals()
                  repair_steps.append("Fixed normals")

                  # Check if watertight now
                  if mesh.is_watertight:
                      volume = float(mesh.volume)
                      repair_steps.append("Watertight after basic repairs")
                      self.repaired_count += 1
                      return True, volume, ' <pipe> '.join(repair_steps)

                  # Step 4: Fill holes
                  mesh.fill_holes()
                  repair_steps.append("Filled holes")

                  # Step 5: Final cleanup
                  mesh.remove_degenerate_faces()
                  mesh.remove_unreferenced_vertices()

                  # Final check
                  if mesh.is_watertight:
                      volume = float(mesh.volume)
                      repair_steps.append("Watertight after full repair")
                      self.repaired_count += 1
                      return True, volume, ' <pipe> '.join(repair_steps)
                  else:
                      repair_steps.append(f"Still not watertight")
                      return False, None, ' <pipe> '.join(repair_steps)

              except Exception as e:
                  repair_steps.append(f"Repair error: {str(e)}")
                  return False, None, ' <pipe> '.join(repair_steps)

          def convert_mesh_via_obj(self, fme_mesh):
              """Convert FME mesh to trimesh via OBJ format"""
              try:
                  obj_lines = []

                  num_vertices = fme_mesh.numVertices()
                  for i in range(num_vertices):
                      vertex = fme_mesh.getVertexAt(i)
                      # getVertexAt returns a tuple for FMEMesh
                      if isinstance(vertex, (tuple, list)):
                          x, y, z = vertex[0], vertex[1], vertex[2] if len(vertex) > 2 else 0.0
                      else:
                          # If it's an FMEPoint, use getXYZ()
                          coords = vertex.getXYZ()
                          x, y, z = coords[0], coords[1], coords[2]

                      obj_lines.append(f"v {x} {y} {z}")

                  # Create faces (assuming triangulated mesh)
                  num_triangles = num_vertices // 3
                  for i in range(num_triangles):
                      v1 = i * 3 + 1
                      v2 = i * 3 + 2
                      v3 = i * 3 + 3
                      if v3 <= num_vertices:
                          obj_lines.append(f"f {v1} {v2} {v3}")

                  obj_string = "\n".join(obj_lines)
                  mesh = trimesh.load(io.StringIO(obj_string), file_type='obj', process=True)

                  if hasattr(mesh, 'geometry'):
                      meshes = list(mesh.geometry.values())
                      mesh = meshes[0] if len(meshes) == 1 else trimesh.util.concatenate(meshes)

                  return mesh

              except Exception as e:
                  return None

          def close(self):
              # Write summary
              try:
                  with open('mesh_processing_summary.txt', 'w') as f:
                      f.write(f"Processing completed.\n")
                      f.write(f"Total features: {self.feature_count}\n")
                      f.write(f"Volumes calculated: {self.volumes_calculated}\n")
                      f.write(f"Repaired: {self.repaired_count}\n")
                      f.write(f"Failed: {self.failed_count}\n")
                      if self.feature_count > 0:
                          f.write(f"Success rate: {self.volumes_calculated/self.feature_count*100:.1f}%\n")
              except:
                  pass
    PYTHONSYMBOL = FeatureProcessor
    -> AttributeManager
Note: Expose new attributes
AttributeManager
    USER_EXPOSED_ATTRIBUTES = Error,geodb_oid,mesh_bbox_max_x,mesh_bbox_max_y,mesh_bbox_max_z,mesh_bbox_min_x,mesh_bbox_min_y,mesh_bbox_min_z,mesh_face_count,mesh_is_watertight,mesh_original_watertight,mesh_vertex_count,mesh_volume,mesh_was_repaired,OBJECTID,UUID,OBJEKTART,NAME_KOMPLETT,GEBAEUDE_NUTZUNG,GRUND_AENDERUNG,HERKUNFT,HERKUNFT_JAHR,HERKUNFT_MONAT,ORIGINAL_HERKUNFT,ERSTELLUNG_JAHR,ERSTELLUNG_MONAT,REVISION_JAHR,REVISION_MONAT,DATUM_AENDERUNG,DATUM_ERSTELLUNG,DACH_MAX,DACH_MIN,GELAENDEPUNKT,GESAMTHOEHE,EGID,GEBAEUDEEINHEIT,error,face_count,geodb_type,input_geometry_type,is_watertight,vertex_count,volume,conversion_method,repair_details,building_height,estimated_wall_perimeter,footprint_area,horizontal_faces_count,max_z,min_z,roof_area,roof_complexity,sloped_area,sloped_faces_count,surface_analysis_error,total_surface_area,vertical_faces_count,wall_area
    -> BulkAttributeRenamer
Note: Prefix: / _mesh
BulkAttributeRenamer
    ATTRCHOICE_ACTION = SELECTED
    ATTRLIST = conversion_method error face_count geodb_oid geodb_type input_geometry_type is_watertight repair_details vertex_count volume
    MODE_CHOICE = RENAME
    PATTERN_ACTION_DISP = ADDPREFIX
    REPLACE_STR = mesh_
    ATTRCHOICE = Selected Attributes
    -> PythonCaller_2
Note: Python: / Calculate areas for repaired meshes - roof, walls, footprint
PythonCaller_2
    PYTHONSOURCE:
      import fmeobjects
      import trimesh
      import numpy as np
      import io

      class FeatureProcessor(object):
          def __init__(self):
              self.feature_count = 0
              # Tolerance for determining horizontal/vertical faces (in degrees)
              self.horizontal_tolerance = 10.0  # Faces within 10 degrees of horizontal
              self.vertical_tolerance = 10.0    # Faces within 10 degrees of vertical

          def input(self, feature):
              self.feature_count += 1

              # Process the feature
              self.process_building_surfaces(feature)

          def get_point_coords(self, point):
              """Extract coordinates from FMEPoint using getXYZ()"""
              try:
                  coords = point.getXYZ()
                  return [float(coords[0]), float(coords[1]), float(coords[2])]
              except Exception as e:
                  raise Exception(f"Failed to extract coordinates: {str(e)}")

          def geometry_to_trimesh(self, geometry):
              """Convert FME geometry to trimesh"""
              try:
                  # If it's already a mesh
                  if isinstance(geometry, fmeobjects.FMEMesh):
                      return self.convert_mesh_via_obj(geometry)

                  # If it's a MultiSurface
                  elif isinstance(geometry, fmeobjects.FMEMultiSurface):
                      mesh, _ = self.multi_surface_to_trimesh(geometry)
                      return mesh

                  else:
                      return None

              except Exception as e:
                  return None

          def classify_face_orientation(self, normal_z, horizontal_tol_rad, vertical_tol_rad):
              """Classify face as horizontal, vertical, or sloped based on normal Z component"""
              abs_z = abs(normal_z)

              # Check if horizontal (normal pointing up or down)
              if abs_z > np.cos(horizontal_tol_rad):
                  if normal_z > 0:
                      return 'horizontal_up'
                  else:
                      return 'horizontal_down'

              # Check if vertical (normal perpendicular to Z)
              elif abs_z < np.sin(vertical_tol_rad):
                  return 'vertical'

              # Otherwise it's sloped
              else:
                  return 'sloped'

          def process_building_surfaces(self, feature):
              """Analyze building surfaces and calculate areas"""
              try:
                  geometry = feature.getGeometry()
                  if not geometry:
                      feature.setAttribute('surface_analysis_error', 'No geometry')
                      self.pyoutput(feature)
                      return

                  # Convert to trimesh
                  mesh = self.geometry_to_trimesh(geometry)
                  if mesh is None:
                      feature.setAttribute('surface_analysis_error', 'Failed to convert to mesh')
                      self.pyoutput(feature)
                      return

                  # Ensure we have face normals
                  face_normals = mesh.face_normals
                  face_areas = mesh.area_faces

                  # Get face centroids for height analysis
                  face_centroids = mesh.triangles_center

                  # Convert tolerance to radians
                  horizontal_tol_rad = np.radians(self.horizontal_tolerance)
                  vertical_tol_rad = np.radians(self.vertical_tolerance)

                  # Initialize area accumulators
                  roof_area = 0.0
                  footprint_area = 0.0
                  wall_area = 0.0
                  sloped_area = 0.0

                  # Lists to store face info for detailed analysis
                  horizontal_faces = []
                  vertical_faces = []
                  sloped_faces = []

                  # Classify each face
                  for i, (normal, area, centroid) in enumerate(zip(face_normals, face_areas, face_centroids)):
                      orientation = self.classify_face_orientation(
                          normal[2], horizontal_tol_rad, vertical_tol_rad
                      )

                      if orientation == 'horizontal_up' or orientation == 'horizontal_down':
                          horizontal_faces.append({
                              'index': i,
                              'area': area,
                              'z': centroid[2],
                              'normal_z': normal[2]
                          })
                      elif orientation == 'vertical':
                          vertical_faces.append({
                              'index': i,
                              'area': area,
                              'z': centroid[2]
                          })
                          wall_area += area
                      else:  # sloped
                          sloped_faces.append({
                              'index': i,
                              'area': area,
                              'z': centroid[2],
                              'normal_z': normal[2]
                          })
                          sloped_area += area

                  # Process horizontal faces to separate roof and footprint
                  if horizontal_faces:
                      # Sort by Z coordinate
                      horizontal_faces.sort(key=lambda x: x['z'])

                      # Find the threshold between footprint and roof
                      # Use the lowest 10% of horizontal face height as footprint threshold
                      z_values = [f['z'] for f in horizontal_faces]
                      min_z = min(z_values)
                      max_z = max(z_values)
                      z_range = max_z - min_z

                      # Threshold: anything within 10% of the lowest horizontal face is footprint
                      footprint_threshold = min_z + 0.1 * z_range if z_range > 0.01 else min_z + 0.1

                      for face in horizontal_faces:
                          if face['z'] <= footprint_threshold:
                              footprint_area += face['area']
                          else:
                              roof_area += face['area']

                  # Calculate total surface area
                  total_area = float(mesh.area)

                  # Set attributes
                  feature.setAttribute('roof_area', float(roof_area))
                  feature.setAttribute('footprint_area', float(footprint_area))
                  feature.setAttribute('wall_area', float(wall_area))
                  feature.setAttribute('sloped_area', float(sloped_area))
                  feature.setAttribute('total_surface_area', total_area)

                  # Additional statistics
                  feature.setAttribute('horizontal_faces_count', len(horizontal_faces))
                  feature.setAttribute('vertical_faces_count', len(vertical_faces))
                  feature.setAttribute('sloped_faces_count', len(sloped_faces))

                  # Building height (from lowest to highest point)
                  if len(mesh.vertices) > 0:
                      z_coords = mesh.vertices[:, 2]
                      building_height = float(np.max(z_coords) - np.min(z_coords))
                      feature.setAttribute('building_height', building_height)
                      feature.setAttribute('min_z', float(np.min(z_coords)))
                      feature.setAttribute('max_z', float(np.max(z_coords)))

                  # Perimeter estimation (sum of wall area divided by average height)
                  if wall_area > 0 and 'building_height' in locals():
                      estimated_perimeter = wall_area / building_height if building_height > 0 else 0
                      feature.setAttribute('estimated_wall_perimeter', float(estimated_perimeter))

                  # Roof complexity indicator (ratio of sloped to total roof area)
                  total_roof_area = roof_area + sloped_area
                  if total_roof_area > 0:
                      roof_complexity = sloped_area / total_roof_area
                      feature.setAttribute('roof_complexity', float(roof_complexity))

                  # Clear any previous errors
                  feature.setAttribute('surface_analysis_error', None)

                  self.pyoutput(feature)

              except Exception as e:
                  feature.setAttribute('surface_analysis_error', f'Processing error: {str(e)}')
                  self.pyoutput(feature)

          def multi_surface_to_trimesh(self, multi_surface):
              """Convert FMEMultiSurface to trimesh (simplified version)"""
              try:
                  all_vertices = []
                  all_faces = []
                  vertex_offset = 0

                  num_parts = multi_surface.numParts()

                  for i in range(num_parts):
                      try:
                          surface = multi_surface.getPartAt(i)
                          area = None
                          boundary = None

                          if hasattr(surface, 'getAsArea'):
                              area = surface.getAsArea()
                              if area and hasattr(area, 'getBoundaryAsCurve'):
                                  boundary = area.getBoundaryAsCurve()

                          if boundary and boundary.numPoints() >= 3:
                              points = []
                              for j in range(boundary.numPoints()):
                                  pt = boundary.getPointAt(j)
                                  coords = self.get_point_coords(pt)
                                  points.append(coords)

                              # Remove duplicate last point if closed
                              if len(points) > 3:
                                  if (abs(points[0][0] - points[-1][0]) < 1e-6 and
                                      abs(points[0][1] - points[-1][1]) < 1e-6 and
                                      abs(points[0][2] - points[-1][2]) < 1e-6):
                                      points = points[:-1]

                              all_vertices.extend(points)

                              # Fan triangulation
                              num_verts = len(points)
                              for j in range(1, num_verts - 1):
                                  all_faces.append([
                                      vertex_offset,
                                      vertex_offset + j,
                                      vertex_offset + j + 1
                                  ])

                              vertex_offset += num_verts

                      except Exception:
                          continue

                  if all_vertices and all_faces:
                      mesh = trimesh.Trimesh(
                          vertices=np.array(all_vertices),
                          faces=np.array(all_faces),
                          process=True
                      )
                      return mesh, None
                  else:
                      return None, None

              except Exception:
                  return None, None

          def convert_mesh_via_obj(self, fme_mesh):
              """Convert FME mesh to trimesh via OBJ format"""
              try:
                  obj_lines = []

                  num_vertices = fme_mesh.numVertices()
                  for i in range(num_vertices):
                      vertex = fme_mesh.getVertexAt(i)
                      if isinstance(vertex, (tuple, list)):
                          x, y, z = vertex[0], vertex[1], vertex[2] if len(vertex) > 2 else 0.0
                      else:
                          coords = vertex.getXYZ()
                          x, y, z = coords[0], coords[1], coords[2]

                      obj_lines.append(f"v {x} {y} {z}")

                  # Create faces
                  num_triangles = num_vertices // 3
                  for i in range(num_triangles):
                      v1 = i * 3 + 1
                      v2 = i * 3 + 2
                      v3 = i * 3 + 3
                      if v3 <= num_vertices:
                          obj_lines.append(f"f {v1} {v2} {v3}")

                  obj_string = "\n".join(obj_lines)
                  mesh = trimesh.load(io.StringIO(obj_string), file_type='obj', process=True)

                  if hasattr(mesh, 'geometry'):
                      meshes = list(mesh.geometry.values())
                      mesh = meshes[0] if len(meshes) == 1 else trimesh.util.concatenate(meshes)

                  return mesh

              except Exception:
                  return None

          def close(self):
              # Summary
              pass
    PYTHONSYMBOL = FeatureProcessor
    -> AttributeManager_2
Note: Expose new attributes
AttributeManager_2
    USER_EXPOSED_ATTRIBUTES = Error,geodb_oid,mesh_bbox_max_x,mesh_bbox_max_y,mesh_bbox_max_z,mesh_bbox_min_x,mesh_bbox_min_y,mesh_bbox_min_z,mesh_face_count,mesh_is_watertight,mesh_original_watertight,mesh_vertex_count,mesh_volume,mesh_was_repaired,OBJECTID,UUID,OBJEKTART,NAME_KOMPLETT,GEBAEUDE_NUTZUNG,GRUND_AENDERUNG,HERKUNFT,HERKUNFT_JAHR,HERKUNFT_MONAT,ORIGINAL_HERKUNFT,ERSTELLUNG_JAHR,ERSTELLUNG_MONAT,REVISION_JAHR,REVISION_MONAT,DATUM_AENDERUNG,DATUM_ERSTELLUNG,DACH_MAX,DACH_MIN,GELAENDEPUNKT,GESAMTHOEHE,EGID,GEBAEUDEEINHEIT,error,face_count,geodb_type,input_geometry_type,is_watertight,vertex_count,volume,conversion_method,repair_details,building_height,estimated_wall_perimeter,footprint_area,horizontal_faces_count,max_z,min_z,roof_area,roof_complexity,sloped_area,sloped_faces_count,surface_analysis_error,total_surface_area,vertical_faces_count,wall_area,mesh_conversion_method,mesh_error,mesh_geodb_oid,mesh_geodb_type,mesh_input_geometry_type,mesh_repair_details
    -> BulkAttributeRenamer_2
Note: Prefix: / _area
BulkAttributeRenamer_2
    ATTRCHOICE_ACTION = SELECTED
    ATTRLIST = building_height estimated_wall_perimeter footprint_area horizontal_faces_count max_z min_z roof_area roof_complexity sloped_area sloped_faces_count surface_analysis_error total_surface_area vertical_faces_count wall_area
    MODE_CHOICE = RENAME
    PATTERN_ACTION_DISP = ADDPREFIX
    REPLACE_STR = area_
    ATTRCHOICE = Selected Attributes
    -> FeatureWriter [Output]
Note: OUTPUT: / Excel File
FeatureWriter
    DATASET = C:\Users\DavidRasner\Downloads\3D Buildings.xlsx
    DATASET_ATTR = _dataset
    FEATURE_TYPE_LIST_ATTR = _feature_types
    FORMAT = XLSXW
    TOTAL_FEATURES_WRITTEN_ATTR = _total_features_written
    XLSXW_ALWAYS_CREATE_FEATURE_TYPES = NO
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = Yes
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = No
    XLSXW_WRITER_MODE = Insert

FME custom transformer MeshBuilder
Takes sets of 3D Polygons or Surfaces containing polygon part(s), and creates Mesh (IFMEMesh) features for each set. All the attributes and coordinate system of the first feature for each set will be propagated to the Mesh feature built from the set.
    If the input feature doesn't have a geometry which can be used as a part of mesh, it will be output via the <Rejected> port.
    Notes:
    1. This transformer just collects 3D Polygon parts from the input features and assembles them into Mesh geometries without any cleaning up manipulations (e.g. snapping, repairing self-intersections, validating planarity etc.). That is, it's not guaranteed that the resultant Meshes are topologically clean.
    2. A Polygon that contains arc segments in its boundary may bring resulting unexpected Mesh shape, but this transformer won't check whether the input Polygons have arc segments. Consider using the ArcStroker beforehand if the input features might have such a Polygon.
    3. Although Mesh (IFMEMesh) geometry represents a surface consisting of multiple polygonal faces, its internal data structure doesn't contain Polygon geometries as its parts. Therefore, a feature that has a Mesh geometry will be rejected, if you send it to this transformer.
Parameters
    Group By
    :
    This parameter allows you to select attributes that define groups (sets) of input features. The features belonging to a group have the same values in the specified attributes, and Meshes will be created for each group.
    Donuts Manipulation
    :
    By default, this transformer assumes that all the input geometries are Polygons (i.e. no holes) or Surfaces containing polygon part(s) only. If the input features might have a Donut or a Surface containing donut part(s), select one of "Keep Holes" or "Drop Holes" for this parameter.

Parameters:
- GROUP_ATTRS =   # " " Group By
- DONUTS_MANIP = NONE   # Holes,KEEP_HOLES%Drop Holes,DROP_HOLES Donuts Manipulation

Input (input)
    -> GeometryFilter
GeometryFilter
    BREAK_AGG_BOOL = 0
    GEOM_PORTS = AREA SURFACE
    BREAK_AGG = No
    GEOM_PORT_NAMES = Area Surface
    AREA -> GeometryFilter_AREA_-__Tester
    SURFACE -> GeometryFilter_AREA_-__Tester
    <UNFILTERED> -> Tester_FAILED_-___Rejected_
GeometryFilter_AREA_-__Tester: Junction
    -> Tester
Note: Tester [Tester] / Test Description: Reject Non-3D features / TEST @Dimension() = 3 / Condition: OR
Tester
    BOOL_OP = OR
    TEST_CLAUSE = TEST @Dimension() = 3
    TEST_MODE = Automatic
    PASSED -> ParameterFetcher
    FAILED -> Tester_FAILED_-___Rejected_
Note: Tester_2 [Tester] / Test Description: "" / TEST $(DONUTS_MANIP) != NONE / Condition: OR
Tester_2
    BOOL_OP = OR
    TEST_CLAUSE = TEST $(DONUTS_MANIP) != NONE
    TEST_MODE = Automatic
    PASSED -> Deaggregator
    FAILED -> GeometryPartExtractor_2
Note: Extract Polygon Parts
GeometryPartExtractor_2
    EXTRACTTYPE = EXTRACT_PART
    GQUERY:
      for $geom in //geometry
      where $geom/@fme_geometry_type = 'IFMEPolygon'
      return number($geom/@fme_id)
    EXTRACTTYPE_PARAM = Extract
    PROCESSED -> PythonCaller
    UNTOUCHED -> <Rejected> (output)
Note: Create Mesh
PythonCaller
    PYTHONSOURCE:
      # 2016-04-04, Takashi Iijima,  Original Implementation

      import fme
      import fmeobjects

      class MeshBuilder(object):
          def __init__(self):
              self.parts = {} # key: group ID, value: list of parts (coordinates lists) belonging to the group
              self.firstPart = {} # key: group ID, value: first part feature of the group

          def input(self, feature):
              id = feature.getAttribute('__meshbuilder.group_id')
              coords = []
              for c in feature.getAllCoordinates():
                  if len(coords) == 0 or c != coords[-1]:
                      coords.append(c)
              if 3 < len(coords) and coords[0] == coords[-1]:
                  if id in self.parts:
                      self.parts[id].append(coords[:-1])
                  else:
                      self.parts[id] = [coords[:-1]]
                      self.firstPart[id] = feature

          def close(self):
              for id in sorted(self.parts.keys()):
                  mesh = fmeobjects.FMEMesh()
                  vertices = {} # key: tuple (x, y, z), value: index of the vertex
                  for coordinates in self.parts[id]:
                      indices = []
                      for coord in coordinates:
                          if coord not in vertices:
                              vertices[coord] = mesh.numVertices()
                              mesh.appendVertex(*coord)
                          indices.append(vertices[coord])
                      mesh.addMeshPart(0, indices + [indices[0]], None, None)
                  self.firstPart[id].setGeometry(mesh)
                  self.pyoutput(self.firstPart[id])
    PYTHONSYMBOL = MeshBuilder
    -> Mesh (output)
Mesh (output)
Tester_FAILED_-___Rejected_: Junction
    -> <Rejected> (output)
<Rejected> (output)

Bookmark: Set Group ID
ParameterFetcher
    ATTR_LIST = __meshbuilder.group_attrs {$(GROUP_ATTRS)}
    -> TclCaller
TclCaller
    SRC:
      proc setGroupId {} {
          set values {}
          foreach attr [FME_GetAttribute "__meshbuilder.group_attrs"] {
              if {![FME_AttributeExists $attr]} {
                  lappend values "\a"
              } elseif {[FME_IsAttributeNull $attr]} {
                  lappend values "\b"
              } else {
                  lappend values [FME_GetAttribute $attr]
              }
          }
          return [join $values "_"]
      }
    TCLPROG = setGroupId
    VAL_ATTR = __meshbuilder.group_id
    -> Tester_2

Bookmark: Donuts Manipulation - Keep Holes or Drop Holes
Deaggregator
    EXPLODE_INSTANCES = No
    LIST_ATTR_MODE_LOOKUP = LEAN
    RECURSIVE = Yes
    SPLIT_COMPOSITES = No
    MODE = Flatten All Levels
    DEAGGREGATED -> GeometryPartExtractor
Note: Extract Donut Parts
GeometryPartExtractor
    EXTRACTTYPE = EXTRACT_PART
    GQUERY:
      for $geom in //geometry
      where $geom/@fme_geometry_type = 'IFMEDonut'
      return number($geom/@fme_id)
    EXTRACTTYPE_PARAM = Extract
    PROCESSED -> HoleCounter
    UNTOUCHED -> GeometryPartExtractor_2
HoleCounter
    CNT_ATTR = __meshbuilder.hole_count
    -> Tester_3
Note: Tester_3 [Tester] / Test Description: "" / TEST $(DONUTS_MANIP) = KEEP_HOLES / TEST 0 < <at>Value(__meshbuilder.hole_count) / Condition: AND
Tester_3
    BOOL_OP = AND
    TEST_CLAUSE:
      TEST $(DONUTS_MANIP) = KEEP_HOLES
      TEST 0 < @Value(__meshbuilder.hole_count)
    TEST_MODE = Automatic
    PASSED -> Triangulator
    FAILED -> DonutHoleExtractor
Triangulator
    TRIANGLES -> Deaggregator_2
Deaggregator_2
    EXPLODE_INSTANCES = No
    LIST_ATTR_MODE_LOOKUP = LEAN
    RECURSIVE = Yes
    SPLIT_COMPOSITES = No
    MODE = Flatten All Levels
    DEAGGREGATED -> Deaggregator_2_DEAGGREGATED_-__PythonCaller
DonutHoleExtractor
    DEAGGREGATE_INPUT = Yes
    OUTERSHELL -> Deaggregator_2_DEAGGREGATED_-__PythonCaller
Deaggregator_2_DEAGGREGATED_-__PythonCaller: Junction
    -> PythonCaller
