FME workspace Base Worker FME.fmw

Creator
    GEOMTYPE = Geometry Object
    NUM = 1
    CREATED -> FeatureReader [INITIATOR]
Note: Gebäude
FeatureReader
    ATTRIBUTES = cppt,"BFSNr,Kategorie,Nummer,Koordinate,Hoehe,Punktzeichen,Begehbar,Kanton,fid",dprsf,"BFSNr,NBIdent,Nummer,EGRIS_EGRID,Vollstaendigkeit,Art,Flaeche,Gueltigkeit,Kanton,fid",dprsfproj,"BFSNr,NBIdent,Nummer,EGRIS_EGRID,Vollstaendigkeit,Art,Flaeche,Kanton,fid",hadr,"BFSNr,Hausnummer,Gebaeudename,GWR_EGID,GWR_EDID,Strassenname,PLZ,Zusatzziffern,Ortschaftsname,Ori,Loc,Kanton,fid",lcobj,"BFSNr,Typ,Text,Art,Ori,Loc,Kanton,fid",lcsf,"BFSNr,Qualitaet,Art,GWR_EGID,Kanton,fid",lcsfproj,"BFSNr,Qualitaet,Art,GWR_EGID,Kanton,fid",lnna,"BFSNr,Kategorie,Name,Ori,Loc,Kanton,fid",locpos,"BFSNr,Strassenname,Ori,Loc,Kanton,fid",mbsf,"BFSNr,Name,Kanton,fid",osbp,"BFSNr,Gueltigkeit,Punktzeichen,Kanton,fid",osnr,"BFSNr,NBIdent,Nummer,Ori,Loc,Dif,Kanton,fid",osnrproj,"BFSNr,NBIdent,Nummer,Ori,Loc,Dif,Kanton,fid",plli,"BFSNr,Betreiber,Medium,Gueltigkeit,Sichtbarkeit,Kanton,fid",plna,"BFSNr,Betreiber,Ori,Loc,Kanton,fid",plsf,"BFSNr,Betreiber,Medium,Gueltigkeit,Kanton,fid",resf,"BFSNr,NBIdent,Nummer,EGRIS_EGRID,Vollstaendigkeit,Flaeche,Gueltigkeit,Kanton,fid",resfhl,"BFSNr,Kanton,fid",resfproj,"BFSNr,NBIdent,Nummer,EGRIS_EGRID,Vollstaendigkeit,Flaeche,Kanton,fid",slide,"BFSNr,NBIdent,Identifikator,Name,Gueltiger_Eintrag,Kanton,fid",slideobj,"BFSNr,NBIdent,Identifikator,Name,Ori,Loc,Kanton,fid",soli,"BFSNr,Gueltigkeit,Art,Qualitaet,Kanton,fid",soobj,"BFSNr,Typ,Text,Art,Ori,Loc,Kanton,fid",sopt,"BFSNr,Gueltigkeit,Art,Qualitaet,Ori,Kanton,fid",sosf,"BFSNr,Gueltigkeit,Art,Qualitaet,GWR_EGID,Kanton,fid",tbbp,"BFSNr,Gueltigkeit,Punktzeichen,Hoheitsgrenzpunkt,Kanton,fid",tbli,"Typ,Gueltigkeit,Kanton,fid"
    ATTR_ACCUM_MODE = Only Use Result
    CLIP_TO_ENVELOPE = NO
    COMBINE_GEOM = Use Result
    DATASET = C:\Users\DavidRasner\Downloads\av_lv95_bern\geopackage\av_2056.gpkg
    FEATURETYPES = lcsf
    FORMAT = OGCGEOPACKAGE
    GEOMETRY_TYPES = cppt,"""wkb_geometry,fme_point""",dprsf,"""wkb_geometry,fme_arc,fme_area,fme_collection,fme_line,fme_point,fme_solid""",dprsfproj,"""wkb_geometry,fme_area""",hadr,"""wkb_geometry,fme_point""",lcobj,"""wkb_geometry,fme_point""",lcsf,"""wkb_geometry,fme_arc,fme_area,fme_collection,fme_line,fme_point,fme_solid""",lcsfproj,"""wkb_geometry,fme_area""",lnna,"""wkb_geometry,fme_point""",locpos,"""wkb_geometry,fme_point""",mbsf,"""wkb_geometry,fme_area""",osbp,"""wkb_geometry,fme_point""",osnr,"""wkb_geometry,fme_point""",osnrproj,"""wkb_geometry,fme_point""",plli,"""wkb_geometry,fme_line""",plna,"""wkb_geometry,fme_point""",plsf,"""wkb_geometry,fme_arc,fme_area,fme_collection,fme_line,fme_point,fme_solid""",resf,"""wkb_geometry,fme_arc,fme_area,fme_collection,fme_line,fme_point,fme_solid""",resfhl,"""wkb_geometry,fme_line""",resfproj,"""wkb_geometry,fme_arc,fme_area,fme_collection,fme_line,fme_point,fme_solid""",slide,"""wkb_geometry,fme_area""",slideobj,"""wkb_geometry,fme_point""",soli,"""wkb_geometry,fme_line""",soobj,"""wkb_geometry,fme_point""",sopt,"""wkb_geometry,fme_point""",sosf,"""wkb_geometry,fme_area""",tbbp,"""wkb_geometry,fme_point""",tbli,"""wkb_geometry,fme_line"""
    INITIATOR_FIRST_OUTPUT = default
    INTERACT = NONE
    MAX_FEATURES = 2000
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    WHERE = "Art" = "Gebaeude"
    lcsf -> HTTPCaller
    lcsf -> FeatureReader_3 [INITIATOR]
    lcsf -> CoordinateSystemSetter_3
Note: Buildings / Gebäude / GET GWR
HTTPCaller
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api3.geo.admin.ch/rest/services/ech/MapServer/find?layer=ch.bfs.gebaeude_wohnungs_register&searchText=@Value(GWR_EGID)&searchField=egid&returnGeometry=false
    TRANSFER_TIMEOUT_LENGTH = 90
    USE_COOKIES = No
    VERIFY_SSL_CERTIFICATES = Yes
    -> JSONExtractor
JSONExtractor
    EXTRACT_QUERY_TABLE = gkode json["results"][0]["attributes"]["gkode"] gkodn json["results"][0]["attributes"]["gkodn"] label json["results"][0]["attributes"]["label"] gkat json["results"][0]["attributes"]["gkat"] gstat json["results"][0]["attributes"]["gstat"] featureId json["results"][0]["attributes"]["featureId"] strname json["results"][0]["attributes"]["strname"][0] deinr json["results"][0]["attributes"]["deinr"] dplz4 json["results"][0]["attributes"]["dplz4"] dplzname json["results"][0]["attributes"]["dplzname"] gdekt json["results"][0]["attributes"]["gdekt"] gbauj json["results"][0]["attributes"]["gbauj"] gbaup json["results"][0]["attributes"]["gbaup"] garea json["results"][0]["attributes"]["garea"] gastw json["results"][0]["attributes"]["gastw"]
    JSON_DOCUMENT = @Value(_response_body)
    READ_FROM_FILE = NO
    EVALUATED -> BulkAttributeRenamer_2
Note: Add Prefix for Maintanability
BulkAttributeRenamer_2
    ATTRCHOICE_ACTION = NONPROTECTEDFME
    MODE_CHOICE = RENAME
    PATTERN_ACTION_DISP = ADDPREFIX
    REPLACE_STR = GWR_
    ATTRCHOICE = All Attributes
    -> CoordinateSystemSetter
Note: LV95
CoordinateSystemSetter
    COORDSYS = CH1903Plus_1.LV95/01
    -> Reprojector
Note: LV95 to LL-WGS84
Reprojector
    DEST = LL-WGS84
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> FeatureJoiner [LEFT]
    REPROJECTED -> VertexCreator
VertexCreator
    MEASURE_TYPE_LOOKUP = CONTINUOUS
    MODE = REPLACE
    REMOVE_ATTRIBUTES = No
    XVAL = @Value(GWR_gkode)
    YVAL = @Value(GWR_gkodn)
    MEASURE_TYPE = Continuous
    MODE_NAME = Replace with Point
    -> CoordinateExtractor
CoordinateExtractor
    IND = 0
    RECURSIVE = No
    X_ATTR = lon
    Y_ATTR = lat
    Z_ATTR = _z
    MODE = Specify Coordinate
    -> FeatureJoiner [RIGHT]
FeatureJoiner
    ATTR_CONFLICT_RES_LOOKUP = USE_LEFT
    GEOMETRY_HANDLING_LOOKUP = USE_LEFT
    JOIN_KEYS = GWR_fid GWR_fid AUTO
    JOIN_MODE = Left
    ATTR_CONFLICT_RES = Prefer Left
    GEOMETRY_HANDLING = Prefer Left
    JOINED -> AttributeCreator
AttributeCreator
    ATTR_TABLE:
      SET_TO egid (varchar(200)) = @Value(GWR_GWR_EGID)
      SET_TO label (varchar(200)) = @Value(GWR_label)
      SET_TO category (varchar(200)) = @Value(GWR_gkat)
      SET_TO source_fid (varchar(200)) = @Value(GWR_fid)
      SET_TO status (varchar(200)) = @Value(GWR_gstat)
      SET_TO country (varchar(7)) = Schweiz
      SET_TO region (varchar(200)) = @Value(GWR_gdekt)
      SET_TO postal_code (varchar(200)) = @Value(GWR_dplz4)
      SET_TO city (varchar(200)) = @Value(GWR_dplzname)
      SET_TO street (varchar(200)) = @Value(GWR_strname)
      SET_TO street_nr (varchar(200)) = @Value(GWR_deinr)
      SET_TO construction_year (varchar(200)) = @Value(GWR_gbauj)
      SET_TO construction_period (varchar(200)) = @Value(GWR_gbaup)
      SET_TO floors_total (varchar(200)) = @Value(GWR_gastw)
      SET_TO area_footprint_m2 (varchar(200)) = @Value(GWR_garea)
    -> AttributeKeeper
AttributeKeeper
    CREATE_BULK_MODE_FEATURES = NO
    KEEP_ATTRS = egid,lat,lon,label,category,source_fid,city,country,postal_code,region,status,street,street_nr,construction_year,area_footprint_m2,floors_total,construction_period
    -> StringReplacer_2
Note: Replace "null"
StringReplacer_2
    CASE = NO
    FIND_TEXT = (?i)\bnull\b
    NO_MATCH = _FME_NO_OP_
    REGEXP = YES
    SRC_ATTRS = area_footprint_m2,category,city,construction_period,construction_year,country,egid,floors_total,label,lat,lon,postal_code,region,source_fid,status,street,street_nr
    -> StringReplacer_3
StringReplacer_3
    CASE = NO
    FIND_TEXT = ^\s*$<pipe>[^0-9.\-]
    NO_MATCH = _FME_NO_OP_
    REGEXP = YES
    REPLACE_TEXT = 0
    SRC_ATTRS = floors_total,area_footprint_m2,construction_year
    -> FeatureWriter [Output]
Note: Upsert / source_fid
FeatureWriter
    DATASET = Supabase Dav
    DATASET_ATTR = _dataset
    FEATURE_TYPE_LIST_ATTR = _feature_types
    FORMAT = POSTGIS
    POSTGIS_ALWAYS_CREATE_FEATURE_TYPES = NO
    POSTGIS_BULK_COPY = YES
    POSTGIS_CASE_CONTROL_ATTR_NAMES = lower
    POSTGIS_CASE_CONTROL_FT_NAMES = none
    POSTGIS_COORDINATE_SYSTEM_GRANULARITY = FEATURE_TYPE
    POSTGIS_GENERIC_GEOMETRY = yes
    POSTGIS_NAMED_CONNECTION = Supabase Dav
    POSTGIS_SPATIAL_COLUMN_NAME = geog
    POSTGIS_SPATIAL_COLUMN_TYPE = geography
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written
Note: Landcover / Bodenabdeckung
CoordinateSystemSetter_3
    COORDSYS = CH1903Plus_1.LV95/01
    -> GeographicAreaCalculator_2
Note: area_polygon_m2
GeographicAreaCalculator_2
    AREA_ATTR = area_polygon_m2
    AreaMult = 1
    -> Reprojector_3
Note: LL-WGS84
Reprojector_3
    DEST = LL-WGS84
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> BulkAttributeRenamer_3
Note: Add Prefix for Maintanability
BulkAttributeRenamer_3
    ATTRCHOICE_ACTION = NONPROTECTEDFME
    MODE_CHOICE = RENAME
    PATTERN_ACTION_DISP = ADDPREFIX
    REPLACE_STR = AV_
    ATTRCHOICE = All Attributes
    -> AttributeCreator_4
AttributeCreator_4
    ATTR_TABLE:
      SET_TO egid (varchar(200)) = @Value(AV_GWR_EGID)
      SET_TO source_fid (varchar(200)) = @Value(AV_fid)
      SET_TO area_m2 (varchar(200)) = @Value(AV_area_polygon_m2)
    -> AttributeKeeper_3
AttributeKeeper_3
    CREATE_BULK_MODE_FEATURES = NO
    KEEP_ATTRS = egid,source_fid,area_m2
    -> FeatureWriter_5 [Output]
Note: Upsert / source_fid
FeatureWriter_5
    DATASET = Supabase Dav
    DATASET_ATTR = _dataset
    FEATURE_TYPE_LIST_ATTR = _feature_types
    FORMAT = POSTGIS
    POSTGIS_ALWAYS_CREATE_FEATURE_TYPES = NO
    POSTGIS_BULK_COPY = YES
    POSTGIS_CASE_CONTROL_ATTR_NAMES = lower
    POSTGIS_CASE_CONTROL_FT_NAMES = none
    POSTGIS_COORDINATE_SYSTEM_GRANULARITY = FEATURE_TYPE
    POSTGIS_GENERIC_GEOMETRY = yes
    POSTGIS_NAMED_CONNECTION = Supabase Dav
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written
Note: Parcels / Grundstücke
FeatureReader_3
    ATTRIBUTES = cppt,"BFSNr,Kategorie,Nummer,Koordinate,Hoehe,Punktzeichen,Begehbar,Kanton,fid",dprsf,"BFSNr,NBIdent,Nummer,EGRIS_EGRID,Vollstaendigkeit,Art,Flaeche,Gueltigkeit,Kanton,fid",dprsfproj,"BFSNr,NBIdent,Nummer,EGRIS_EGRID,Vollstaendigkeit,Art,Flaeche,Kanton,fid",hadr,"BFSNr,Hausnummer,Gebaeudename,GWR_EGID,GWR_EDID,Strassenname,PLZ,Zusatzziffern,Ortschaftsname,Ori,Loc,Kanton,fid",lcobj,"BFSNr,Typ,Text,Art,Ori,Loc,Kanton,fid",lcsf,"BFSNr,Qualitaet,Art,GWR_EGID,Kanton,fid",lcsfproj,"BFSNr,Qualitaet,Art,GWR_EGID,Kanton,fid",lnna,"BFSNr,Kategorie,Name,Ori,Loc,Kanton,fid",locpos,"BFSNr,Strassenname,Ori,Loc,Kanton,fid",mbsf,"BFSNr,Name,Kanton,fid",osbp,"BFSNr,Gueltigkeit,Punktzeichen,Kanton,fid",osnr,"BFSNr,NBIdent,Nummer,Ori,Loc,Dif,Kanton,fid",osnrproj,"BFSNr,NBIdent,Nummer,Ori,Loc,Dif,Kanton,fid",plli,"BFSNr,Betreiber,Medium,Gueltigkeit,Sichtbarkeit,Kanton,fid",plna,"BFSNr,Betreiber,Ori,Loc,Kanton,fid",plsf,"BFSNr,Betreiber,Medium,Gueltigkeit,Kanton,fid",resf,"BFSNr,NBIdent,Nummer,EGRIS_EGRID,Vollstaendigkeit,Flaeche,Gueltigkeit,Kanton,fid",resfhl,"BFSNr,Kanton,fid",resfproj,"BFSNr,NBIdent,Nummer,EGRIS_EGRID,Vollstaendigkeit,Flaeche,Kanton,fid",slide,"BFSNr,NBIdent,Identifikator,Name,Gueltiger_Eintrag,Kanton,fid",slideobj,"BFSNr,NBIdent,Identifikator,Name,Ori,Loc,Kanton,fid",soli,"BFSNr,Gueltigkeit,Art,Qualitaet,Kanton,fid",soobj,"BFSNr,Typ,Text,Art,Ori,Loc,Kanton,fid",sopt,"BFSNr,Gueltigkeit,Art,Qualitaet,Ori,Kanton,fid",sosf,"BFSNr,Gueltigkeit,Art,Qualitaet,GWR_EGID,Kanton,fid",tbbp,"BFSNr,Gueltigkeit,Punktzeichen,Hoheitsgrenzpunkt,Kanton,fid",tbli,"Typ,Gueltigkeit,Kanton,fid"
    ATTR_ACCUM_MODE = Only Use Result
    COMBINE_GEOM = Use Result
    DATASET = C:\Users\DavidRasner\Downloads\av_lv95_bern\geopackage\av_2056.gpkg
    FEATURETYPES = resf
    FORMAT = OGCGEOPACKAGE
    GEOMETRY_TYPES = cppt,"""wkb_geometry,fme_point""",dprsf,"""wkb_geometry,fme_arc,fme_area,fme_collection,fme_line,fme_point,fme_solid""",dprsfproj,"""wkb_geometry,fme_area""",hadr,"""wkb_geometry,fme_point""",lcobj,"""wkb_geometry,fme_point""",lcsf,"""wkb_geometry,fme_arc,fme_area,fme_collection,fme_line,fme_point,fme_solid""",lcsfproj,"""wkb_geometry,fme_area""",lnna,"""wkb_geometry,fme_point""",locpos,"""wkb_geometry,fme_point""",mbsf,"""wkb_geometry,fme_area""",osbp,"""wkb_geometry,fme_point""",osnr,"""wkb_geometry,fme_point""",osnrproj,"""wkb_geometry,fme_point""",plli,"""wkb_geometry,fme_line""",plna,"""wkb_geometry,fme_point""",plsf,"""wkb_geometry,fme_arc,fme_area,fme_collection,fme_line,fme_point,fme_solid""",resf,"""wkb_geometry,fme_arc,fme_area,fme_collection,fme_line,fme_point,fme_solid""",resfhl,"""wkb_geometry,fme_line""",resfproj,"""wkb_geometry,fme_arc,fme_area,fme_collection,fme_line,fme_point,fme_solid""",slide,"""wkb_geometry,fme_area""",slideobj,"""wkb_geometry,fme_point""",soli,"""wkb_geometry,fme_line""",soobj,"""wkb_geometry,fme_point""",sopt,"""wkb_geometry,fme_point""",sosf,"""wkb_geometry,fme_area""",tbbp,"""wkb_geometry,fme_point""",tbli,"""wkb_geometry,fme_line"""
    INITIATOR_FIRST_OUTPUT = default
    INTERACT = WITHIN
    MAX_FEATURES = 10
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = NO
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    resf -> DuplicateFilter
Note: Remove Duplicate by / Unique FID
DuplicateFilter
    INPUT_ORDERED_CHOICE_LOOKUP = NO
    KEYATTR = fid
    INPUT_ORDERED_CHOICE = No
    UNIQUE -> GeographicAreaCalculator
Note: area_polygon_m2
GeographicAreaCalculator
    AREA_ATTR = area_polygon_m2
    AreaMult = 1
    -> Reprojector_2
Note: LV95 to WGS84
Reprojector_2
    DEST = LL-WGS84
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> BulkAttributeRenamer
Note: Add Prefix for Maintanability
BulkAttributeRenamer
    ATTRCHOICE_ACTION = NONPROTECTEDFME
    MODE_CHOICE = RENAME
    PATTERN_ACTION_DISP = ADDPREFIX
    REPLACE_STR = AV_
    ATTRCHOICE = All Attributes
    -> AttributeCreator_3
Note: Target DB schema
AttributeCreator_3
    ATTR_TABLE:
      SET_TO egrid (varchar(200)) = @Value(AV_EGRIS_EGRID)
      SET_TO source_fid (varchar(200)) = @Value(AV_fid)
      SET_TO area_m2 (varchar(200)) = @Value(AV_area_polygon_m2)
      SET_TO area_surface_m2 (varchar(200))
      SET_TO status (varchar(200))
      SET_TO municipality_nr (varchar(200)) = @Value(AV_NBIdent)
      SET_TO parcel_number (varchar(200)) = @Value(AV_Nummer)
    -> AttributeKeeper_2
Note: Keep / Target DB schema
AttributeKeeper_2
    CREATE_BULK_MODE_FEATURES = NO
    KEEP_ATTRS = egrid,area_m2,area_surface_m2,source_fid,municipality_nr,parcel_number
    -> StringReplacer
StringReplacer
    CASE = NO
    FIND_TEXT = ^\s*$<pipe>[^0-9.\-]
    NO_MATCH = _FME_NO_OP_
    REGEXP = YES
    REPLACE_TEXT = 0
    SRC_ATTRS = area_m2,area_surface_m2
    -> AttributeRounder
AttributeRounder
    PLACES = 0
    ROUND_TYPE_TCL = round
    SRC_ATTRS = area_m2 area_surface_m2
    ROUND_TYPE = Nearest
    -> FeatureWriter_3 [Output]
Note: Upsert / source_fid
FeatureWriter_3
    DATASET = Supabase Dav
    DATASET_ATTR = _dataset
    FEATURE_TYPE_LIST_ATTR = _feature_types
    FORMAT = POSTGIS
    POSTGIS_ALWAYS_CREATE_FEATURE_TYPES = NO
    POSTGIS_BULK_COPY = YES
    POSTGIS_CASE_CONTROL_ATTR_NAMES = lower
    POSTGIS_CASE_CONTROL_FT_NAMES = none
    POSTGIS_COORDINATE_SYSTEM_GRANULARITY = FEATURE_TYPE
    POSTGIS_GENERIC_GEOMETRY = yes
    POSTGIS_NAMED_CONNECTION = Supabase Dav
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written
