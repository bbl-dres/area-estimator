FME workspace Volume Estimator FME.fmw

Creator_2
    GEOMTYPE = Geometry Object
    NUM = 1
    CREATED -> FeatureReader_3 [INITIATOR]
Note: PostGIS
FeatureReader_3
    ATTRIBUTES = public.buildings,"id,label,egid,source_fid,parcel_id,created_at,updated_at,country,region,city,postal_code,street,street_nr,status,category,class,roof_form,construction_year,renovation_year,dwellings_count,area_footprint_m2,area_floor_total_m2,area_floor_above_ground_m2,area_floor_below_ground_m2,area_floor_net_m2,area_ebf_m2,area_roof_m2,area_wall_m2,area_accuracy,floors_total,floors_above,floors_below,floors_accuracy,volume_total_m3,volume_above_ground_m3,volume_below_ground_m3,volume_accuracy,elevation_base_m,height_mean_m,height_max_m,heating_type,heating_source,water_heating_type,water_heating_source,municipality_nr,municipality_name,heritage_category,heritage_inventory_nr,zone_main,zone_type,construction_period,lon,lat"
    ATTR_ACCUM_MODE = Only Use Result
    CLIP_TO_ENVELOPE = NO
    COMBINE_GEOM = Use Result
    DATASET = Supabase Dav
    FEATURETYPES = public.buildings
    FORMAT = POSTGIS
    GEOMETRY_TYPES = public.buildings,"""geog,fme_area"""
    INITIATOR_FIRST_OUTPUT = default
    INTERACT = NONE
    ORDER_RESULTS = No
    OUTPUT_ADD_SCHEMA_ATTRIBUTES = NO
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = Supabase Dav
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    public.buildings -> AttributeKeeper_3
AttributeKeeper_3
    CREATE_BULK_MODE_FEATURES = NO
    KEEP_ATTRS = id
    -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(id) = 6767",@Value(id) = 6767
    @Value(id) = 6767 -> Reprojector_2
Reprojector_2
    DEST = CH1903Plus_1.LV95/01
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> BoundingBoxReplacer_3
    REPROJECTED -> Clipper [CLIPPER]
    REPROJECTED -> Clipper_2 [CLIPPER]
    REPROJECTED -> BoundingBoxReplacer_2
Note: Aggregate by file_id
Aggregator_2
    ACCUM_ATTRS = None
    AGGREGATE_TYPE = Homogeneous Collection (If Possible)
    GROUP_BY = tile_id
    MODE = Geometry - Assemble One Level
    SEP = ,
    AGGREGATE -> FeatureJoiner [LEFT]
    AGGREGATE -> FeatureJoiner_4 [LEFT]
BoundingBoxReplacer_2
    BBANGLE = _angle
    BBTYPE = MINBB
    BOXTYPE = 2D Oriented Bounding Box
    BOX -> Tiler_2
Tiler_2
    CLEANING_TOLERANCE_LOOKUP = AUTO
    COLUMN_ATTR = _column
    DUPLICATE_ON_TILE_BORDERS = NO
    INVALID_PART_HANDLING = REJECT_WHOLE_FEATURE
    MISSING_MEASURE_VALUES_LOOKUP = LINEAR_INTERPOLATION
    MISSING_Z_VALUES_LOOKUP = PLANAR_INTERPOLATION
    ROW_ATTR = _row
    STARTINGCORNER = BOTTOM_LEFT
    TILE_HEIGHT = 1
    TILE_WIDTH = 1
    TILING_TYPE = TILE_SIZE
    CLEANING_TOLERANCE = Automatic
    MISSING_MEASURE_VALUES = Linear Interpolation
    MISSING_Z_VALUES = Planar Interpolation
    TILED -> Clipper_2 [CANDIDATE]
Clipper_2
    ADD_NODATA = YES
    BOUNDARY_CASES = INSIDE
    CLEANING_TOLERANCE_LOOKUP = AUTO
    CLIPPED_ATTR = _clipped
    CLIPPERS_FIRST = NO
    GENERATE_LIST = NO
    GROUP_BY = id
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
Creator_3
    GEOMTYPE = Geometry Object
    NUM = 1
    CREATED -> FeatureReader_5 [INITIATOR]
    CREATED -> FeatureReader_4 [INITIATOR]
    CREATED -> FeatureReader_2 [INITIATOR]
    CREATED -> FeatureReader_7 [INITIATOR]
Note: List files in directory / Höhenmodell / SwissAlti3D / tiff
FeatureReader_4
    ATTRIBUTES = PATH,"path_unix,path_windows,path_rootname,path_filename,path_extension,path_directory_unix,path_directory_windows,path_type,fme_geometry{0}"
    ATTR_ACCUM_MODE = Only Use Result
    COMBINE_GEOM = Use Result
    DATASET = D:\SwissAlti3D
    FORMAT = PATH
    INITIATOR_FIRST_OUTPUT = default
    ORDER_RESULTS = No
    OUTPUT_ADD_SCHEMA_ATTRIBUTES = NO
    OUTPUT_FEATURES_DISPLAY = Schema and Data Features
    PATH_GLOB_PATTERN = *
    PATH_HIDDEN_FILES = INCLUDE
    PATH_NO_EMPTY_PROPERTIES = YES
    PATH_OFFSET_DATETIME = yes
    PATH_RECURSE_DIRECTORIES = NO
    PATH_RETRIEVE_FILE_PROPERTIES = NO
    PATH_TYPE = ANY
    PATH_USE_NON_STRING_ATTR = yes
    PATH -> TestFilter
Note: tiff
TestFilter
    DEFAULT_VALUE = <UNFILTERED>
    PASSED_TEST_GROUP_OUTPUT = FIRST
    TEST_LIST = "BOOL_OP,OR,COMPOSITE_TEST,""""""1"""""",TEST_CLAUSE,TEST @Value(path_extension) = tif",@Value(path_extension) = tif
    @Value(path_extension) = tif -> AttributeSplitter_2
AttributeSplitter_2
    ATTR_NAME = path_filename
    DELIMITER = _
    DROP_EMPTY_PARTS = NO
    LIST_NAME = _list
    TRIM_TYPE = BOTH
    -> AttributeCreator_4
Note: Swisstopo tile_id
AttributeCreator_4
    ATTR_TABLE = SET_TO tile_id (varchar(200)) = @Value(_list{2})
    -> AttributeKeeper
AttributeKeeper
    CREATE_BULK_MODE_FEATURES = NO
    KEEP_ATTRS = tile_id,path_windows
    -> FeatureJoiner [RIGHT]
FeatureJoiner
    ATTR_CONFLICT_RES_LOOKUP = USE_LEFT
    GEOMETRY_HANDLING_LOOKUP = USE_LEFT
    JOIN_KEYS = tile_id tile_id AUTO
    JOIN_MODE = Inner
    ATTR_CONFLICT_RES = Prefer Left
    GEOMETRY_HANDLING = Prefer Left
    JOINED -> FeatureReader_6 [INITIATOR]
    UNJOINED_LEFT -> FeatureJoiner_2 [LEFT]
FeatureReader_6
    ATTR_ACCUM_MODE = Only Use Result
    CLIP_TO_ENVELOPE = NO
    COMBINE_GEOM = Use Result
    DATASET = @Value(path_windows)
    FORMAT = GEOTIFF
    GEOTIFF_APPLY_GCPS = NO
    GEOTIFF_FEATURE_TYPE_NAME = FORMAT_NAME
    GEOTIFF_IGNORE_RASTER_TYPE_KEY = No
    GEOTIFF_LENIENT_READ = Yes
    GEOTIFF_NATIVELY_HANDLED_WEBSERVICES = s3connector,azurestorage,google-cloud-storage
    GEOTIFF_PREFER_FILE_CS_UNITS = Yes
    GEOTIFF_READER_META_ATTRIBUTES = fme_dataset fme_basename
    GEOTIFF_READ_OFFSETS_IN_CS_UNITS = No
    GEOTIFF_SCALE_COLOR_TO_STANDARD_BIT_DEPTH = YES
    GEOTIFF_USE_SEARCH_ENVELOPE = NO
    INITIATOR_FIRST_OUTPUT = default
    INTERACT = NONE
    ORDER_RESULTS = No
    OUTPUT_ADD_SCHEMA_ATTRIBUTES = NO
    OUTPUT_FEATURES_DISPLAY = Schema and Data Features
    <OTHER> -> RasterMosaicker
RasterMosaicker
    ACCUM_ATTRS = ONE
    INTERPOLATION_TYPE = NearestNeighbor
    MERGE_PALETTES_NAME = Yes
    NODATA_OVERWRITE = No
    OVERLAPPING_VALUES = last
    SNAPPING_TYPE = RESAMPLE
    ACCUM_ATTRS_NAME = Use Attributes From One Feature
    INTERPOLATION_TYPE_NAME = Nearest Neighbor
    MERGE_PALETTES = Yes
    SNAPPING_TYPE_NAME = Resample
    -> PointOnRasterValueExtractor_2 [RASTER]
Note: CSV / Höhenmodell / SwissAlti3D
FeatureReader_5
    ATTRIBUTES = CSV,col0
    ATTR_ACCUM_MODE = Only Use Result
    CLIP_TO_ENVELOPE = NO
    COMBINE_GEOM = Use Result
    CSV2_CASE_SENSITIVE_FIELD_NAMES = Yes
    CSV2_CHUNK_SIZE = 100000
    CSV2_DATA_START_LINE = 1
    CSV2_DATE_INPUT_FORMAT = ISO
    CSV2_DELIMITER = auto
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 0
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = D:\SwissAlti3D\ch.swisstopo.swissalti3d-tCFHFRVc.csv
    FORMAT = CSV2
    INITIATOR_FIRST_OUTPUT = default
    INTERACT = NONE
    ORDER_RESULTS = No
    OUTPUT_ADD_SCHEMA_ATTRIBUTES = NO
    OUTPUT_FEATURES_DISPLAY = Schema and Data Features
    CSV -> FilenamePartExtractor
FilenamePartExtractor
    EXTENSION_ATTR = _extension
    FULLNAME_ATTR = _filename
    SRC_ATTR = @Value(col0)
    -> AttributeSplitter_3
AttributeSplitter_3
    ATTR_NAME = col0
    DELIMITER = _
    DROP_EMPTY_PARTS = NO
    LIST_NAME = _list
    TRIM_TYPE = BOTH
    -> AttributeCreator_3
Note: Swisstopo tile_id
AttributeCreator_3
    ATTR_TABLE = SET_TO tile_id (varchar(200)) = @Value(_list{4})
    -> FeatureJoiner_2 [RIGHT]
FeatureJoiner_2
    ATTR_CONFLICT_RES_LOOKUP = USE_LEFT
    GEOMETRY_HANDLING_LOOKUP = USE_LEFT
    JOIN_KEYS = tile_id tile_id AUTO
    JOIN_MODE = Inner
    ATTR_CONFLICT_RES = Prefer Left
    GEOMETRY_HANDLING = Prefer Left
    JOINED -> AttributeCreator_6
AttributeCreator_6
    ATTR_TABLE = SET_TO _filename (buffer) = D:\SwissAlti3D\@Value(_filename)
    -> HTTPCaller_2
Note: Download Missing TIFs
HTTPCaller_2 [off]
    CLIENT_CERTIFICATE_TYPE = NONE
    CONNECTION_TIMEOUT_LENGTH = 60
    ERROR_ATTR = _error
    FILE_PATH_ATTR = _response_file_path
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    OUTPUT_FILENAME = @Value(_filename)
    REDIRECT_AUTH = ORIGINAL_DOMAIN_ONLY
    RESPONSE_TYPE = File
    STATUS_CODE_ATTR = _http_status_code
    TARGET_URL = @Value(col0)
    TRANSFER_TIMEOUT_LENGTH = 90
    USE_COOKIES = No
    VERIFY_SSL_CERTIFICATES = Yes
Note: List files in directory / Höhenmodell / swissSURFACE3D / tiff
FeatureReader_2
    ATTRIBUTES = PATH,"path_unix,path_windows,path_rootname,path_filename,path_extension,path_directory_unix,path_directory_windows,path_type,fme_geometry{0}"
    ATTR_ACCUM_MODE = Only Use Result
    COMBINE_GEOM = Use Result
    DATASET = D:\swissSURFACE3D
    FORMAT = PATH
    INITIATOR_FIRST_OUTPUT = default
    ORDER_RESULTS = No
    OUTPUT_ADD_SCHEMA_ATTRIBUTES = NO
    OUTPUT_FEATURES_DISPLAY = Schema and Data Features
    PATH_GLOB_PATTERN = *
    PATH_HIDDEN_FILES = INCLUDE
    PATH_NO_EMPTY_PROPERTIES = YES
    PATH_OFFSET_DATETIME = yes
    PATH_RECURSE_DIRECTORIES = NO
    PATH_RETRIEVE_FILE_PROPERTIES = NO
    PATH_TYPE = ANY
    PATH_USE_NON_STRING_ATTR = yes
    PATH -> TestFilter_2
Note: tiff
TestFilter_2
    DEFAULT_VALUE = <UNFILTERED>
    PASSED_TEST_GROUP_OUTPUT = FIRST
    TEST_LIST = "BOOL_OP,OR,COMPOSITE_TEST,""""""1"""""",TEST_CLAUSE,TEST @Value(path_extension) = tif",@Value(path_extension) = tif
    @Value(path_extension) = tif -> AttributeSplitter_4
AttributeSplitter_4
    ATTR_NAME = path_filename
    DELIMITER = _
    DROP_EMPTY_PARTS = NO
    LIST_NAME = _list
    TRIM_TYPE = BOTH
    -> AttributeCreator_7
Note: Swisstopo tile_id
AttributeCreator_7
    ATTR_TABLE = SET_TO tile_id (varchar(200)) = @Value(_list{2})
    -> AttributeKeeper_2
AttributeKeeper_2
    CREATE_BULK_MODE_FEATURES = NO
    KEEP_ATTRS = tile_id,path_windows
    -> FeatureJoiner_4 [RIGHT]
FeatureJoiner_4
    ATTR_CONFLICT_RES_LOOKUP = USE_LEFT
    GEOMETRY_HANDLING_LOOKUP = USE_LEFT
    JOIN_KEYS = tile_id tile_id AUTO
    JOIN_MODE = Inner
    ATTR_CONFLICT_RES = Prefer Left
    GEOMETRY_HANDLING = Prefer Left
    JOINED -> FeatureReader_8 [INITIATOR]
    UNJOINED_LEFT -> FeatureJoiner_3 [LEFT]
FeatureReader_8
    ATTR_ACCUM_MODE = Only Use Result
    CLIP_TO_ENVELOPE = NO
    COMBINE_GEOM = Use Result
    DATASET = @Value(path_windows)
    FORMAT = GEOTIFF
    GEOTIFF_APPLY_GCPS = NO
    GEOTIFF_FEATURE_TYPE_NAME = FORMAT_NAME
    GEOTIFF_IGNORE_RASTER_TYPE_KEY = No
    GEOTIFF_LENIENT_READ = Yes
    GEOTIFF_NATIVELY_HANDLED_WEBSERVICES = s3connector,azurestorage,google-cloud-storage
    GEOTIFF_PREFER_FILE_CS_UNITS = Yes
    GEOTIFF_READER_META_ATTRIBUTES = fme_dataset fme_basename
    GEOTIFF_READ_OFFSETS_IN_CS_UNITS = No
    GEOTIFF_SCALE_COLOR_TO_STANDARD_BIT_DEPTH = YES
    GEOTIFF_USE_SEARCH_ENVELOPE = NO
    INITIATOR_FIRST_OUTPUT = default
    INTERACT = NONE
    ORDER_RESULTS = No
    OUTPUT_ADD_SCHEMA_ATTRIBUTES = NO
    OUTPUT_FEATURES_DISPLAY = Schema and Data Features
    <OTHER> -> RasterMosaicker_2
RasterMosaicker_2
    ACCUM_ATTRS = ONE
    INTERPOLATION_TYPE = NearestNeighbor
    MERGE_PALETTES_NAME = Yes
    NODATA_OVERWRITE = No
    OVERLAPPING_VALUES = last
    SNAPPING_TYPE = RESAMPLE
    ACCUM_ATTRS_NAME = Use Attributes From One Feature
    INTERPOLATION_TYPE_NAME = Nearest Neighbor
    MERGE_PALETTES = Yes
    SNAPPING_TYPE_NAME = Resample
    -> PointOnRasterValueExtractor_3 [RASTER]
GeometryReplacer
    KIND = fmebinary
    REMOVE_ATTRIBUTE = Yes
    SOURCE = @Value(_geometry)
    KIND_LONG = FME Binary
    -> StatisticsCalculator
    -> FeatureJoiner_5 [LEFT]
StatisticsCalculator
    ATTR_ACCUM_MODE = None
    CALCULATION_MODE = NUMERIC
    FEAT_STATS = ele_base,NUMERIC_MODE,MIN,MAX,,,MEAN,,,,,,,,
    GROUP_BY = id
    SUMMARY -> FeatureJoiner_5 [RIGHT]
FeatureJoiner_5
    ATTR_CONFLICT_RES_LOOKUP = USE_LEFT
    GEOMETRY_HANDLING_LOOKUP = USE_LEFT
    JOIN_KEYS = id id AUTO
    JOIN_MODE = Inner
    ATTR_CONFLICT_RES = Prefer Left
    GEOMETRY_HANDLING = Prefer Left
    JOINED -> Extruder
Extruder
    DIRECTION_LOOKUP = VERTICAL
    DISTANCE = @Value(ele_top)-@Value(ele_base.min)
    DIRECTION = Vertical
    EXTRUDED -> VolumeCalculator
VolumeCalculator
    MULT = 1
    SET_TRAIT = No
    VOLUME_ATTR = _volume
    -> StatisticsCalculator_2
StatisticsCalculator_2
    ATTR_ACCUM_MODE = None
    CALCULATION_MODE = NUMERIC
    FEAT_STATS = _volume,NUMERIC_MODE,,,,SUM,,,,,,,,,;ele_top,NUMERIC_MODE,,MAX,,,MEAN,,,,,,,,;ele_base,NUMERIC_MODE,MIN,,,,,,,,,,,,
    GROUP_BY = id
    SUMMARY -> AttributeCreator
AttributeCreator
    ATTR_TABLE:
      SET_TO volume_total_m3 (varchar(200)) = @Value(_volume.sum)
      SET_TO volume_above_ground_m3 (varchar(200)) = @Value(_volume.sum)
      SET_TO elevation_base_m (varchar(200)) = @Value(ele_base.min)
      SET_TO height_mean_m (real64) = @Evaluate(@Value(ele_top.mean)-@Value(ele_base.min))
      SET_TO height_max_m (real64) = @Evaluate(@Value(ele_top.max)-@Value(ele_base.min))
    -> AttributeKeeper_4
AttributeKeeper_4
    CREATE_BULK_MODE_FEATURES = NO
    KEEP_ATTRS = elevation_base_m,height_max_m,height_mean_m,id,volume_above_ground_m3,volume_total_m3
    -> AttributeRounder
AttributeRounder
    PLACES = 1
    ROUND_TYPE_TCL = round
    SRC_ATTRS = elevation_base_m height_max_m height_mean_m volume_above_ground_m3 volume_total_m3
    ROUND_TYPE = Nearest
    -> FeatureWriter [Output]
FeatureWriter
    DATASET = Supabase Dav
    DATASET_ATTR = _dataset
    FEATURE_TYPE_LIST_ATTR = _feature_types
    FORMAT = POSTGIS
    POSTGIS_ALWAYS_CREATE_FEATURE_TYPES = NO
    POSTGIS_BULK_COPY = YES
    POSTGIS_CASE_CONTROL_ATTR_NAMES = lower
    POSTGIS_CASE_CONTROL_FT_NAMES = none
    POSTGIS_COORDINATE_SYSTEM_GRANULARITY = FEATURE_TYPE
    POSTGIS_GENERIC_GEOMETRY = yes
    POSTGIS_NAMED_CONNECTION = Supabase Dav
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written
Note: CSV / Höhenmodell / swissSURFACE3D
FeatureReader_7
    ATTRIBUTES = CSV,col0
    ATTR_ACCUM_MODE = Only Use Result
    CLIP_TO_ENVELOPE = NO
    COMBINE_GEOM = Use Result
    CSV2_CASE_SENSITIVE_FIELD_NAMES = Yes
    CSV2_CHUNK_SIZE = 100000
    CSV2_DATA_START_LINE = 1
    CSV2_DATE_INPUT_FORMAT = ISO
    CSV2_DELIMITER = auto
    CSV2_DELIMITER_DETECTION_ALGORITHM = EQUAL_FIELDS_PER_LINE
    CSV2_ENCODING = windows-1252
    CSV2_ENFORCE_STRICT_SCHEMA = No
    CSV2_FEATURE_TYPE_NAME = FORMAT_NAME
    CSV2_FIELD_NAMES_LINE = 0
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = No
    CSV2_SCAN_ADDITIONAL_FIELDS = No
    CSV2_SCAN_MAX_ROWS = 250000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = D:\swissSURFACE3D\ch.swisstopo.swisssurface3d-raster-4KshK73K.csv
    FORMAT = CSV2
    INITIATOR_FIRST_OUTPUT = default
    INTERACT = NONE
    ORDER_RESULTS = No
    OUTPUT_ADD_SCHEMA_ATTRIBUTES = NO
    OUTPUT_FEATURES_DISPLAY = Schema and Data Features
    CSV -> FilenamePartExtractor_2
FilenamePartExtractor_2
    EXTENSION_ATTR = _extension
    FULLNAME_ATTR = _filename
    SRC_ATTR = @Value(col0)
    -> AttributeSplitter_5
AttributeSplitter_5
    ATTR_NAME = col0
    DELIMITER = _
    DROP_EMPTY_PARTS = NO
    LIST_NAME = _list
    TRIM_TYPE = BOTH
    -> AttributeCreator_8
Note: Swisstopo tile_id
AttributeCreator_8
    ATTR_TABLE = SET_TO tile_id (varchar(200)) = @Value(_list{4})
    -> FeatureJoiner_3 [RIGHT]
FeatureJoiner_3
    ATTR_CONFLICT_RES_LOOKUP = USE_LEFT
    GEOMETRY_HANDLING_LOOKUP = USE_LEFT
    JOIN_KEYS = tile_id tile_id AUTO
    JOIN_MODE = Inner
    ATTR_CONFLICT_RES = Prefer Left
    GEOMETRY_HANDLING = Prefer Left
    JOINED -> AttributeCreator_9
AttributeCreator_9
    ATTR_TABLE = SET_TO _filename (buffer) = D:\swissSURFACE3D\@Value(_filename)
    -> HTTPCaller_3
Note: Download Missing TIFs
HTTPCaller_3 [off]
    CLIENT_CERTIFICATE_TYPE = NONE
    CONNECTION_TIMEOUT_LENGTH = 60
    ERROR_ATTR = _error
    FILE_PATH_ATTR = _response_file_path
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    OUTPUT_FILENAME = @Value(_filename)
    REDIRECT_AUTH = ORIGINAL_DOMAIN_ONLY
    RESPONSE_TYPE = File
    STATUS_CODE_ATTR = _http_status_code
    TARGET_URL = @Value(col0)
    TRANSFER_TIMEOUT_LENGTH = 90
    USE_COOKIES = No
    VERIFY_SSL_CERTIFICATES = Yes

Bookmark: Voxel Tiles
BoundingBoxReplacer_3
    BBANGLE = _angle
    BBTYPE = MINBB
    BOXTYPE = 2D Oriented Bounding Box
    BOX -> CenterPointExtractor_2
CenterPointExtractor_2
    CENTX = _inside_x
    CENTY = _inside_y
    CENTZ = _inside_z
    EXTRACTIONMODE = CENTER
    -> Rotator
Rotator
    ANGLE = @Value(_angle)*-1
    XORIG = @Value(_inside_x)
    YORIG = @Value(_inside_y)
    ROTATED -> Tiler
Tiler
    CLEANING_TOLERANCE_LOOKUP = AUTO
    COLUMN_ATTR = _column
    DUPLICATE_ON_TILE_BORDERS = NO
    INVALID_PART_HANDLING = REJECT_WHOLE_FEATURE
    MISSING_MEASURE_VALUES_LOOKUP = LINEAR_INTERPOLATION
    MISSING_Z_VALUES_LOOKUP = PLANAR_INTERPOLATION
    ROW_ATTR = _row
    STARTINGCORNER = BOTTOM_LEFT
    TILE_HEIGHT = 1
    TILE_WIDTH = 1
    TILING_TYPE = TILE_SIZE
    CLEANING_TOLERANCE = Automatic
    MISSING_MEASURE_VALUES = Linear Interpolation
    MISSING_Z_VALUES = Planar Interpolation
    TILED -> Rotator_3
Rotator_3
    ANGLE = @Value(_angle)
    XORIG = @Value(_inside_x)
    YORIG = @Value(_inside_y)
    ROTATED -> Clipper [CANDIDATE]
Clipper
    ADD_NODATA = YES
    BOUNDARY_CASES = INSIDE
    CLEANING_TOLERANCE_LOOKUP = AUTO
    CLIPPED_ATTR = _clipped
    CLIPPERS_FIRST = NO
    GENERATE_LIST = NO
    GROUP_BY = id
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> GeometryExtractor

Bookmark: New Bookmark
GeometryExtractor
    ATTR = _geometry
    KIND = fmebinary
    REMOVE_GEOMETRY = No
    KIND_LONG = FME Binary
    -> CenterPointReplacer_2
CenterPointReplacer_2
    POINTTYPE = CENTER
    POINT -> AttributeCreator_2
Note: Swisstopo tile_id
AttributeCreator_2
    ATTR_TABLE:
      SET_TO tile_E (real64) = @Evaluate(@int(@Value(_inside_x) / 1000))
      SET_TO tile_N (real64) = @Evaluate(@int(@Value(_inside_y) / 1000))
      SET_TO tile_id (varchar(200)) = @Value(tile_E)-@Value(tile_N)
    -> Aggregator_2
    -> PointOnRasterValueExtractor_2 [POINT]

Bookmark: Evaluate
PointOnRasterValueExtractor_2
    INTERPOLATION_TYPE = NearestNeighbor
    INTERPOLATION_TYPE_NAME = Nearest Neighbor
    POINT -> AttributeCreator_5
Note: ele_base
AttributeCreator_5
    ATTR_TABLE = SET_TO ele_base (varchar(200)) = @Value(_band{0}.value)
    -> PointOnRasterValueExtractor_3 [POINT]

Bookmark: Evaluate
PointOnRasterValueExtractor_3
    INTERPOLATION_TYPE = NearestNeighbor
    INTERPOLATION_TYPE_NAME = Nearest Neighbor
    POINT -> AttributeCreator_10
Note: ele_top
AttributeCreator_10
    ATTR_TABLE = SET_TO ele_top (varchar(200)) = @Value(_band{0}.value)
    -> GeometryReplacer
